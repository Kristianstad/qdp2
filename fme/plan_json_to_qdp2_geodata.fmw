FME workspace plan_json_to_qdp2_geodata.fmw
Title: Ladar in en detaljplan i plandatabasen qdp2

Parameters:
- SourceDataset_TEXTLINE =   # JSON-fil att läsa in
- SourceDataset_TEXTLINE_3 =   # Fil med beteckningar
- KATALOGVERSION = 2024-05-02   # Välj katalogversion
- ANTECKNING = Importerad 2026-02-26   # Anteckning
- PUBLICERAD = 2   # Publicerad
- AKT =   # Akt LM

Readers:
- TEXTLINE_1: TEXTLINE from $(SourceDataset_TEXTLINE)
- POSTGRES_1: POSTGRES from MSF_geodata_fme_user
- TEXTLINE_2: TEXTLINE from $(SourceDataset_TEXTLINE_3)

Writers:
- POSTGRES_2: POSTGRES to MSF_geodata_fme_user
- POSTGRES_3: POSTGRES to MSF_geodata_fme_user
- POSTGIS_1: POSTGIS to MSF_geodata_fme_user
- POSTGIS_2: POSTGIS to MSF_geodata_fme_user in EPSG:3008
- POSTGRES_4: POSTGRES to MSF_geodata_fme_user
- POSTGRES_5: POSTGRES to MSF_geodata_fme_user
- POSTGIS_3: POSTGIS to MSF_geodata_fme_user
- POSTGRES_6: POSTGRES to MSF_geodata_fme_user

text_line (reader TEXTLINE_2)
    attributes: text_line_data buffer
    -> JSONFrag_beteckning
JSONFrag_beteckning: JSONFragmenter
    EXPLODE_FORMAT = JSON
    EXTRACT_ATTR = Yes
    JSON_ATTR = text_line_data
    JSON_QUERY = json["RegulationInfos"][*]
    NEW_ATTRIBUTES = RegulationID Label Index MainRegulation
    READ_FROM_FILE = NO
    RECURSIVE_LOOKUP = YES
    REJECT_EMPTY_LISTS = YES
    RECURSIVE = Yes
    FRAGMENTS -> JSONFragmenter_3
JSONFragmenter_3
    EXPLODE_FORMAT = JSON
    EXTRACT_ATTR = Yes
    JSON_ATTR = text_line_data
    JSON_QUERY = json["PlacementInfos"][*]
    NEW_ATTRIBUTES = Id Rotation FontSize Location.coordinates{0} Location.coordinates{1}
    READ_FROM_FILE = NO
    RECURSIVE_LOOKUP = YES
    REJECT_EMPTY_LISTS = YES
    RECURSIVE = Yes
    FRAGMENTS -> AttributeManager_2
AttributeManager_2
    ATTR_TABLE:
      REMOVE text_line_data (buffer)
      REMOVE json_type (buffer)
      REMOVE json_index (uint32)
      RENAME_SET_VALUE Id > PlacementId (buffer)
      RENAME_SET_VALUE Location.coordinates{0} > ost_set (buffer)
      RENAME_SET_VALUE Location.coordinates{1} > norr_set (buffer)
    -> FeatureJoiner_5 [RIGHT]
    -> FeatureMerger_3 [SUPPLIER]
text_line (reader TEXTLINE_1)
    attributes: text_line_data buffer
    -> JSONFragmenter_prop
    -> JSONExtractor_plan_uuid
JSONExtractor_plan_uuid
    EXTRACT_QUERY_TABLE = plan_uuid json["features"][0]["properties"]["objektidentitet"]
    JSON_DOCUMENT = @Value(text_line_data)
    READ_FROM_FILE = NO
    EVALUATED -> JSONFragmenter_kvalitet
    EVALUATED -> JSONFragmenter_lage_plan
    EVALUATED -> JSONFragmenter_lage_best
lagesbestamningsmetod (writer POSTGRES_3)
    attributes: lage_id uuid,PrimaryKey, plan_uuid uuid, metod text, variant text, tidpunkt date, skala int4, lagesosakerhet numeric(1000,500)
kvalitet (writer POSTGRES_3)
    attributes: plan_uuid uuid,BTree, digitaliseringsniva text, beskrivning_niva text, korrigerade_granser bool, kval_id uuid,PrimaryKey, kontrollerat_underlag bool
JSONFragmenter_prop
    EXPLODE_FORMAT = JSON
    EXTRACT_ATTR = Yes
    JSON_ATTR = text_line_data
    JSON_QUERY = json["features"][*]["properties"]
    NEW_ATTRIBUTES = feature:typ objektidentitet
    READ_FROM_FILE = NO
    RECURSIVE_LOOKUP = YES
    REJECT_EMPTY_LISTS = YES
    RECURSIVE = Yes
    FRAGMENTS -> FeatureJoiner_5 [LEFT]
    FRAGMENTS -> FeatureMerger_3 [REQUESTOR]
Note: Problem med flera beteckningar på samma bestämmelse. Behöver lösas i db med ny tabell om det ska stödjas.
FeatureJoiner_5 [off]
    ATTR_CONFLICT_RES_LOOKUP = USE_LEFT
    GEOMETRY_HANDLING_LOOKUP = USE_LEFT
    JOIN_KEYS = objektidentitet RegulationID AUTO
    JOIN_MODE = Left
    ATTR_CONFLICT_RES = Prefer Left
    GEOMETRY_HANDLING = Prefer Left
    JOINED -> AttributeFilter
    UNJOINED_RIGHT -> AttributeFilter
FeatureMerger_3
    ATTR_ACCUM_MODE = Merge Supplier
    ATTR_CONFLICT_RES_LOOKUP = REQUESTOR_IF_CONFLICT
    IGNORE_NULLS = No
    JOIN_KEYS = @Value(objektidentitet) @Value(RegulationID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeFilter
    UNMERGED_REQUESTOR -> AttributeFilter
AttributeFilter
    ATTR_NAME = feature:typ
    ATTR_VALUES = detaljplan,användningsbestämmelse,egenskapsbestämmelse,administrativ bestämmelse,<Empty>,<Missing>,<Null>,<Unfiltered>
    PRESERVE_FEATURE_ORDER_LOOKUP = PER_OUTPUT_PORT
    detaljplan -> AttributeExposer
    detaljplan -> JSONFragmenter_beslutsinfo
    detaljplan -> JSONFrag_planb_2
    detaljplan -> JSONFrag_punderlag
    detaljplan -> SQLExecutor [INITIATOR]
    användningsbestämmelse -> FeatureCounter
    egenskapsbestämmelse -> FeatureCounter
    administrativ bestämmelse -> FeatureCounter
underlag (writer POSTGRES_3)
    attributes: dokref_id uuid, namn text, kortnamn text, datum date, handelse text, specifik_ref text, underlag_id uuid,PrimaryKey, plan_uuid uuid, huvudomrade text, underlagstyp text
planbeskrivning (writer POSTGRES_3)
    attributes: dokref_id uuid, namn text, kortnamn text, datum date, handelse text, specifik_ref text, planbeskr_id uuid,PrimaryKey, plan_uuid uuid
referens (writer POSTGRES_3)
    attributes: ref_id serial,PrimaryKey, identitet uuid, namnrymd text, url text, dokref_id uuid, fil text
beslutshandling (writer POSTGRES_4)
    attributes: dokref_id uuid, namn text, kortnamn text, datum date, handelse text, specifik_ref text, beslh_id uuid,PrimaryKey, beslut_id uuid, innehall text
plan (writer POSTGRES_2)
    attributes: plan_uuid uuid,PrimaryKey, objektidentitet uuid, planversion int4, v_giltig_fran timestamp, v_giltig_till timestamp, kommun text, beteckning text, namn text, syfte text, status text, datum_statusforandring date, typ text, anvandbarhet text, anvandbarhet_beskrivning text, akt text, katalogversion text, publicerad int4, kval_id uuid, avgransning text, anteckning text
plan_omr (writer POSTGIS_1)
    attributes: po_uuid uuid,PrimaryKey, plan_uuid uuid,BTree, zmin numeric(1000,500), zmax numeric(1000,500), lagesbestamningsmetod_plan uuid, absolutlagesosakerhetplan numeric(1000,500), tid_lage timestamp, tid_kontroll timestamp, lagesbestamningsmetod_hojd uuid, absolutlagesosakerhethojd numeric(1000,500)
FeatureCounter
    FeatureCounterNewAttrParameter = _numfeatures
    -> AttributeManager_20
    -> AttributeExp_4
Note: Antalet räknade bestämmelser
Junction_2
    -> FeatureJoiner_8 [RIGHT]
beslut (writer POSTGRES_3)
    attributes: beslut_id uuid,PrimaryKey, plan_uuid uuid, instans text, diarienummer_kn text, diareinummer_kf text, beslutstyp text, gk_id uuid, paborjat date, antagande date, lagakraft text, genomforandetid int4, genomforandetid_startar date, arkivid_kn text, foregaende_plans_bet text, berord_doms_malnr text, planbestammelse text
variabel (writer POSTGRES_5)
    attributes: id serial,PrimaryKey, best_uuid uuid,BTree, datatyp text, variabelvarde text, beskrivning text, vardetyp text, enhet text
Note: Bestämmelser
Junction_4
    -> FeatureJoiner_3 [RIGHT]
FeatureJoiner_3
    ATTR_CONFLICT_RES_LOOKUP = USE_LEFT
    GEOMETRY_HANDLING_LOOKUP = USE_LEFT
    JOIN_KEYS = planbestammelsekatalogreferens bk_ref AUTO bestammelsevarde bestammelsevarde AUTO
    JOIN_MODE = Inner
    ATTR_CONFLICT_RES = Use Left
    GEOMETRY_HANDLING = Use Left
    JOINED -> FeatureMerger [REQUESTOR]
FeatureMerger
    ATTR_ACCUM_MODE = Merge Supplier
    ATTR_CONFLICT_RES_LOOKUP = SUPPLIER_IF_CONFLICT
    IGNORE_NULLS = No
    JOIN_KEYS = @Value(objektidentitet) @Value(objektidentitet) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Supplier
    MERGE_TYPE = Attributes Only
    MERGED -> Tester_motiv
    UNMERGED_REQUESTOR -> Tester_motiv
Tester_motiv
    BOOL_OP = OR
    TEST_CLAUSE = TEST planbestammelsebeskrivning.motiv ATTRIBUTE_HAS_A_VALUE ""
    TEST_MODE = TEST
    PASSED -> DuplicateFilter_6
    PASSED -> FeatureJoiner_7 [LEFT]
    FAILED -> AttributeKeeper_5
motiv (writer POSTGRES_4)
    attributes: motiv_id uuid,PrimaryKey, best_uuid uuid, motiv text
FeatureJoiner_7
    ATTR_CONFLICT_RES_LOOKUP = USE_LEFT
    GEOMETRY_HANDLING_LOOKUP = USE_LEFT
    JOIN_KEYS = best_uuid best_uuid AUTO planbestammelsebeskrivning.motiv motiv AUTO
    JOIN_MODE = Left
    ATTR_CONFLICT_RES = Use Left
    GEOMETRY_HANDLING = Use Left
    JOINED -> AttributeKeeper_5
Note: Uppdaterar bestämmelseformuleringar som gäller all användningsform
best (writer POSTGRES_6)
    attributes: best_uuid uuid,PrimaryKey, galler_all_anvandningsform bool
DuplicateFilter_5
    INPUT_ORDERED_CHOICE_LOOKUP = NO
    KEYATTR = best_uuid galler_endast xbest_uuid
    PRESERVE_FEATURE_ORDER_LOOKUP = PER_OUTPUT_PORT
    INPUT_ORDERED_CHOICE = No
    UNIQUE -> FeatureJoiner_endast_y [RIGHT]
    UNIQUE -> FeatureJoiner_endast_l_2 [RIGHT]
    UNIQUE -> FeatureJoiner_endast_p_2 [RIGHT]
egen_best (writer POSTGRES_5)
    attributes: ebest_uuid uuid,PrimaryKey, best_uuid uuid,BTree, o_uuid uuid,BTree, norr numeric(10,3), ost numeric(10,3), rotation numeric(10,3), motiv_id uuid, galler_endast text, avgransning text
AttributeFilter_geomtyp
    ATTR_NAME = typ
    ATTR_VALUES = yta,linje,punkt,<Empty>,<Missing>,<Null>,<Unfiltered>
    PRESERVE_FEATURE_ORDER_LOOKUP = PER_OUTPUT_PORT
    yta -> omr (writer POSTGIS_2)
    linje -> AttributeManager_23
    punkt -> AttributeManager_24
AttributeManager_23
    ATTR_TABLE:
      RENAME_SET_VALUE xbest_uuid > l_uuid
      REMOVE g_uuid
      RENAME_SET_VALUE absolutLagesosakerhetHojd > absolutlagesosakerhethojd
    -> FeatureJoiner_endast_l_2 [LEFT]
FeatureJoiner_endast_l_2
    ATTR_CONFLICT_RES_LOOKUP = USE_LEFT
    GEOMETRY_HANDLING_LOOKUP = USE_LEFT
    JOIN_KEYS = l_uuid xbest_uuid AUTO
    JOIN_MODE = Inner
    ATTR_CONFLICT_RES = Use Left
    GEOMETRY_HANDLING = Use Left
    JOINED -> egenlin (writer POSTGIS_3)
egenlin (writer POSTGIS_3)
    attributes: l_uuid uuid,PrimaryKey, po_uuid uuid,BTree, plan_uuid uuid,BTree, anvandningsform text,BTree, zmin numeric(1000,500), zmax numeric(1000,500), tid_lage timestamp, tid_kontroll timestamp, lagesbestamningsmetod_plan uuid, lagesbestamningsmetod_hojd uuid, absolutlagesosakerhetplan numeric(1000,500), absolutlagesosakerhethojd numeric(1000,500), best_uuid uuid,BTree, motiv_id uuid, galler_endast text, avgransning text
AttributeManager_24
    ATTR_TABLE:
      RENAME_SET_VALUE xbest_uuid > p_uuid
      REMOVE g_uuid
      RENAME_SET_VALUE absolutLagesosakerhetHojd > absolutlagesosakerhethojd
    -> FeatureJoiner_endast_p_2 [LEFT]
FeatureJoiner_endast_p_2
    ATTR_CONFLICT_RES_LOOKUP = USE_LEFT
    GEOMETRY_HANDLING_LOOKUP = USE_LEFT
    JOIN_KEYS = p_uuid xbest_uuid AUTO
    JOIN_MODE = Inner
    ATTR_CONFLICT_RES = Use Left
    GEOMETRY_HANDLING = Use Left
    JOINED -> egenpkt (writer POSTGIS_3)
egenpkt (writer POSTGIS_3)
    attributes: p_uuid uuid,PrimaryKey, po_uuid uuid,BTree, plan_uuid uuid,BTree, anvandningsform text,BTree, zmin numeric(1000,500), zmax numeric(1000,500), tid_lage timestamp, tid_kontroll timestamp, lagesbestamningsmetod_plan uuid, lagesbestamningsmetod_hojd uuid, absolutlagesosakerhetplan numeric(1000,500), absolutlagesosakerhethojd numeric(1000,500), best_uuid uuid,BTree, motiv_id uuid, galler_endast text, avgransning text
omr (writer POSTGIS_2)
    attributes: o_uuid uuid,PrimaryKey, po_uuid uuid,BTree, plan_uuid uuid,BTree, anvandningsform text,BTree, zmin numeric(1000,500), zmax numeric(1000,500), lagesbestamningsmetod_plan uuid, absolutlagesosakerhetplan numeric(1000,500), tid_lage timestamp, absolutlagesosakerhethojd numeric(1000,500), lagesbestamningsmetod_hojd uuid, tid_kontroll timestamp

Bookmark: Lägesbestämning
JSONFragmenter_lage_best
    EXPLODE_FORMAT = JSON
    EXTRACT_ATTR = Yes
    JSON_ATTR = text_line_data
    JSON_QUERY = json["features"][*]["properties"]["bestammelsegeometri"][*]["geometrimetadata"]["lagesbestamningsmetodIPlan"]
    READ_FROM_FILE = NO
    RECURSIVE_LOOKUP = YES
    REJECT_EMPTY_LISTS = YES
    RECURSIVE = Yes
    FRAGMENTS -> AttributeExposer_2
JSONFragmenter_lage_plan
    EXPLODE_FORMAT = JSON
    EXTRACT_ATTR = Yes
    JSON_ATTR = text_line_data
    JSON_QUERY = json["features"][*]["properties"]["plangeometri"][*]["geometrimetadata"]["lagesbestamningsmetodIPlan"]
    READ_FROM_FILE = NO
    RECURSIVE_LOOKUP = YES
    REJECT_EMPTY_LISTS = YES
    RECURSIVE = Yes
    FRAGMENTS -> AttributeExposer_2
AttributeExposer_2
    ATTR_LIST = typ,variant,presentationsskala,lagesosakerhetForReferensobjekt
    -> JSONExtractor
JSONExtractor
    EXTRACT_QUERY_TABLE = tidpunkt json["tidpunktForUnderlagetsFramtagande"]["fran"]
    JSON_DOCUMENT = @Value(text_line_data)
    READ_FROM_FILE = NO
    EVALUATED -> DuplicateFilter_2
DuplicateFilter_2
    INPUT_ORDERED_CHOICE_LOOKUP = NO
    KEYATTR = text_line_data
    PRESERVE_FEATURE_ORDER_LOOKUP = PER_OUTPUT_PORT
    INPUT_ORDERED_CHOICE = No
    UNIQUE -> UUIDlage
UUIDlage: UUIDGenerator
    UUID_ATTR = lage_id
    -> AttributeKeeper_6
    -> AttributeKeeper_3
    -> lagesbestamningsmetod (writer POSTGRES_3)

Bookmark: Planområde
AttributeKeeper_3
    CREATE_BULK_MODE_FEATURES = No
    KEEP_ATTRS = lage_id,text_line_data
    -> FeatureJoiner_2 [RIGHT]
AttributeKeeper
    CREATE_BULK_MODE_FEATURES = No
    KEEP_ATTRS = objektidentitet,text_line_data
    -> JSONFragmenter_2
JSONFragmenter_2
    EXPLODE_FORMAT = JSON
    EXTRACT_ATTR = Yes
    JSON_ATTR = text_line_data
    JSON_QUERY = json["plangeometri"][*]
    READ_FROM_FILE = NO
    RECURSIVE_LOOKUP = YES
    REJECT_EMPTY_LISTS = YES
    RECURSIVE = Yes
    FRAGMENTS -> JSONExtractor_lage_plan_2
JSONExtractor_lage_plan_2
    EXTRACT_QUERY_TABLE = lagesbestPlan json["geometrimetadata"]["lagesbestamningsmetodIPlan"]
    JSON_DOCUMENT = @Value(text_line_data)
    READ_FROM_FILE = NO
    EVALUATED -> JSONExtractor_tid_lage_2
JSONExtractor_tid_lage_2
    EXTRACT_QUERY_TABLE = tid_lage_plan json["geometrimetadata"]["tidpunktForLagesbestamning"]
    JSON_DOCUMENT = @Value(text_line_data)
    READ_FROM_FILE = NO
    EVALUATED -> JSONFragmenter_geom_2
JSONFragmenter_geom_2
    EXPLODE_FORMAT = JSON
    EXTRACT_ATTR = Yes
    JSON_ATTR = text_line_data
    JSON_QUERY = json["geometri"]
    NEW_ATTRIBUTES = typ absolutLagesosakerhetPlan absolutLagesosakerhetHojd dimension koordinatsystemPlan hojdsystem
    READ_FROM_FILE = NO
    RECURSIVE_LOOKUP = YES
    REJECT_EMPTY_LISTS = YES
    RECURSIVE = Yes
    FRAGMENTS -> JSONExtractor_pos
JSONExtractor_pos
    EXTRACT_QUERY_TABLE = position json["position"]
    JSON_DOCUMENT = @Value(text_line_data)
    READ_FROM_FILE = NO
    EVALUATED -> GeometryReplacer
GeometryReplacer
    KIND = GEOJSON
    REMOVE_ATTRIBUTE = Yes
    SOURCE = @Value(position)
    KIND_LONG = GeoJSON
    -> CoordinateSystemSetter
CoordinateSystemSetter
    COORDSYS = @Value(koordinatsystemPlan)
    -> UUIDGenerator
UUIDGenerator
    UUID_ATTR = po_uuid
    -> FeatureJoiner_2 [LEFT]
FeatureJoiner_2
    ATTR_CONFLICT_RES_LOOKUP = USE_LEFT
    GEOMETRY_HANDLING_LOOKUP = USE_LEFT
    JOIN_KEYS = lagesbestPlan text_line_data AUTO
    JOIN_MODE = Inner
    ATTR_CONFLICT_RES = Use Left
    GEOMETRY_HANDLING = Use Left
    JOINED -> AttributeManager_5
    UNJOINED_LEFT -> AttributeManager_5
AttributeManager_5
    ATTR_TABLE:
      RENAME_SET_VALUE objektidentitet > plan_uuid
      RENAME_SET_VALUE absolutLagesosakerhetPlan > absolutlagesosakerhetplan
      RENAME_SET_VALUE lage_id > lagesbestamningsmetod_plan
      SET_TO tid_lage_plan = FME_CONDITIONAL:DEFAULT_VALUE'@DateTimeNow()'BOOL_OP;OR;COMPOSITE_TEST;1;TEST tid_lage_plan ATTRIBUTE_HAS_A_VALUE _FME_BLANK_STRING_'@Value(tid_lage_plan)'FME_NUM_CONDITIONS2___
      SET_TO tid_lage = FME_CONDITIONAL:DEFAULT_VALUE'@DateTimeNow()'BOOL_OP;OR;COMPOSITE_TEST;1;TEST tid_lage_plan ATTRIBUTE_HAS_A_VALUE _FME_BLANK_STRING_'@Value(tid_lage_plan)'FME_NUM_CONDITIONS2___
    -> plan_omr (writer POSTGIS_1)

Bookmark: Bestämmelsegeometri
AttributeKeeper_6
    CREATE_BULK_MODE_FEATURES = No
    KEEP_ATTRS = lage_id,text_line_data
    -> FeatureJoiner_4 [RIGHT]
DuplicateFilter_4
    INPUT_ORDERED_CHOICE_LOOKUP = NO
    KEYATTR = json_geom
    PRESERVE_FEATURE_ORDER_LOOKUP = PER_OUTPUT_PORT
    INPUT_ORDERED_CHOICE = No
    UNIQUE -> UUID_geom
UUID_geom: UUIDGenerator
    UUID_ATTR = g_uuid
    -> AttributeCopier_b_geom
AttributeCopier_b_geom
    ATTR_TABLE = COPY text_line_data > b_geom
    -> JSONExtractor_lage_plan
JSONExtractor_lage_plan
    EXTRACT_QUERY_TABLE = lagesbestPlan json["geometrimetadata"]["lagesbestamningsmetodIPlan"]
    JSON_DOCUMENT = @Value(text_line_data)
    READ_FROM_FILE = NO
    EVALUATED -> JSONExtractor_tid_lage
JSONExtractor_tid_lage
    EXTRACT_QUERY_TABLE = tid_lage_plan json["geometrimetadata"]["tidpunktForLagesbestamning"]
    JSON_DOCUMENT = @Value(text_line_data)
    READ_FROM_FILE = NO
    EVALUATED -> JSONFragmenter_geom
JSONFragmenter_geom
    EXPLODE_FORMAT = JSON
    EXTRACT_ATTR = Yes
    JSON_ATTR = text_line_data
    JSON_QUERY = json["geometri"]
    NEW_ATTRIBUTES = typ absolutLagesosakerhetPlan absolutLagesosakerhetHojd dimension koordinatsystemPlan hojdsystem
    READ_FROM_FILE = NO
    RECURSIVE_LOOKUP = YES
    REJECT_EMPTY_LISTS = YES
    RECURSIVE = Yes
    FRAGMENTS -> JSONExtractor_position
JSONExtractor_position
    EXTRACT_QUERY_TABLE = position json["position"]
    JSON_DOCUMENT = @Value(text_line_data)
    READ_FROM_FILE = NO
    EVALUATED -> GeometryReplacer_2
GeometryReplacer_2
    KIND = GEOJSON
    REMOVE_ATTRIBUTE = Yes
    SOURCE = @Value(position)
    KIND_LONG = GeoJSON
    -> CoordinateSystemSetter_2
CoordinateSystemSetter_2
    COORDSYS = @Value(koordinatsystemPlan)
    -> AttributeKeeper_8
    -> FeatureJoiner_4 [LEFT]
FeatureJoiner_4
    ATTR_CONFLICT_RES_LOOKUP = USE_LEFT
    GEOMETRY_HANDLING_LOOKUP = USE_LEFT
    JOIN_KEYS = lagesbestPlan text_line_data AUTO
    JOIN_MODE = Inner
    ATTR_CONFLICT_RES = Use Left
    GEOMETRY_HANDLING = Use Left
    JOINED -> AttributeManager_6
    UNJOINED_LEFT -> AttributeManager_6
AttributeManager_6
    ATTR_TABLE:
      RENAME_SET_VALUE detaljplan > plan_uuid
      SET_TO anvandningsform = @TitleCase(@Value(anvandningsform))
      RENAME_SET_VALUE absolutLagesosakerhetPlan > absolutlagesosakerhetplan
      RENAME_SET_VALUE lage_id > lagesbestamningsmetod_plan
      SET_TO tid_lage_plan = FME_CONDITIONAL:DEFAULT_VALUE'@DateTimeNow()'BOOL_OP;OR;COMPOSITE_TEST;1;TEST tid_lage_plan ATTRIBUTE_HAS_A_VALUE _FME_BLANK_STRING_'@Value(tid_lage_plan)'FME_NUM_CONDITIONS2___
      SET_TO tid_lage = FME_CONDITIONAL:DEFAULT_VALUE'@DateTimeNow()'BOOL_OP;OR;COMPOSITE_TEST;1;TEST tid_lage_plan ATTRIBUTE_HAS_A_VALUE _FME_BLANK_STRING_'@Value(tid_lage_plan)'FME_NUM_CONDITIONS2___
      SET_TO zmax = FME_CONDITIONAL:DEFAULT_VALUE'_FME_NO_OP_'BOOL_OP;OR;COMPOSITE_TEST;1;TEST @Value(avgransning) = uppåt'@ZValue()'FME_NUM_CONDITIONS2___
      SET_TO zmin = FME_CONDITIONAL:DEFAULT_VALUE'_FME_NO_OP_'BOOL_OP;OR;COMPOSITE_TEST;1;TEST @Value(avgransning) = nedåt'@ZValue()'FME_NUM_CONDITIONS2___
    -> AttributeFilter_geomtyp

Bookmark: Kvalitet
JSONFragmenter_kvalitet
    EXPLODE_FORMAT = JSON
    EXTRACT_ATTR = Yes
    JSON_ATTR = text_line_data
    JSON_QUERY = json["features"][*]["properties"]["kvalitetsbeskrivning"]
    NEW_ATTRIBUTES = digitaliseringsniva beskrivningNiva korrigeradeGranser kontrolleratPlaneringsunderlag
    READ_FROM_FILE = NO
    RECURSIVE_LOOKUP = YES
    REJECT_EMPTY_LISTS = YES
    RECURSIVE = Yes
    FRAGMENTS -> DuplicateFilter
DuplicateFilter
    INPUT_ORDERED_CHOICE_LOOKUP = NO
    KEYATTR = text_line_data
    PRESERVE_FEATURE_ORDER_LOOKUP = PER_OUTPUT_PORT
    INPUT_ORDERED_CHOICE = No
    UNIQUE -> UUIDGenerator_kval
UUIDGenerator_kval
    UUID_ATTR = kval_id
    -> AttributeManager
AttributeManager
    ATTR_TABLE:
      REMOVE json_type
      REMOVE json_index
      RENAME_SET_VALUE beskrivningNiva > beskrivning_niva
      RENAME_SET_VALUE korrigeradeGranser > korrigerade_granser
      RENAME_SET_VALUE kontrolleratPlaneringsunderlag > kontrollerat_underlag
    -> AttributeKeeper_kv_p
    -> AttributeKeeper_kv_b
    -> kvalitet (writer POSTGRES_3)

Bookmark: Plan
AttributeKeeper_kv_p
    CREATE_BULK_MODE_FEATURES = No
    KEEP_ATTRS = id,text_line_data,kval_id
    -> FeatureJoiner [RIGHT]
AttributeExposer
    ATTR_LIST = objektversion,versionGiltigFran,kommun,beteckning,namn,syfte,status,datumStatusforandring,typ,anvandbarhet,beskrivningAnvandbarhet
    -> AttributeKeeper
    -> JSONExtractor_kval
JSONExtractor_kval
    EXTRACT_QUERY_TABLE = kvalitetsbeskrivning json["kvalitetsbeskrivning"]
    JSON_DOCUMENT = @Value(text_line_data)
    READ_FROM_FILE = NO
    EVALUATED -> FeatureJoiner [LEFT]
FeatureJoiner
    ATTR_CONFLICT_RES_LOOKUP = USE_LEFT
    GEOMETRY_HANDLING_LOOKUP = USE_LEFT
    JOIN_KEYS = kvalitetsbeskrivning text_line_data AUTO
    JOIN_MODE = Inner
    ATTR_CONFLICT_RES = Use Left
    GEOMETRY_HANDLING = Use Left
    JOINED -> AttributeManager_15
    UNJOINED_LEFT -> AttributeManager_15
AttributeManager_15
    ATTR_TABLE:
      REMOVE text_line_data
      REMOVE json_type
      REMOVE json_index
      REMOVE feature:typ
      RENAME_SET_VALUE objektversion > planversion
      RENAME_SET_VALUE versionGiltigFran > v_giltig_fran
      RENAME_SET_VALUE kommun = FME_CONDITIONAL:DEFAULT_VALUE'Kristianstad'BOOL_OP;OR;COMPOSITE_TEST;1;TEST kommun ATTRIBUTE_HAS_A_VALUE _FME_BLANK_STRING_'@Value(kommun)'FME_NUM_CONDITIONS2___
      SET_TO namn = FME_CONDITIONAL:DEFAULT_VALUE'Namn?!?'BOOL_OP;OR;COMPOSITE_TEST;1;TEST namn ATTRIBUTE_HAS_A_VALUE _FME_BLANK_STRING_'@Value(namn)'FME_NUM_CONDITIONS2___
      SET_TO syfte = FME_CONDITIONAL:DEFAULT_VALUE'Syfte?!?'BOOL_OP;OR;COMPOSITE_TEST;1;TEST syfte ATTRIBUTE_HAS_A_VALUE _FME_BLANK_STRING_'@Value(syfte)'FME_NUM_CONDITIONS2___
      RENAME_SET_VALUE datumStatusforandring > datum_statusforandring
      RENAME_SET_VALUE beskrivningAnvandbarhet > anvandbarhet_beskrivning
      SET_TO katalogversion = $(KATALOGVERSION)
      SET_TO plan_uuid = @Value(objektidentitet)
      SET_TO akt = $(AKT)
      SET_TO publicerad = $(PUBLICERAD)
      SET_TO anteckning = $(ANTECKNING)
    -> plan (writer POSTGRES_2)

Bookmark: Bestämmelser
AttributeKeeper_kv_b
    CREATE_BULK_MODE_FEATURES = NO
    KEEP_ATTRS = text_line_data,kval_id
    -> FeatureJoiner_b_kv [RIGHT]
AttributeExp_4: AttributeExposer
    ATTR_LIST = detaljplan,planbestammelsekatalogreferens,bestammelseformulering,ursprungligBestammelseformulering,anvandbarhet,beskrivningAnvandbarhet,planbestammelsebeskrivning.motiv,reglerarAnvandningsbestammelse{},sekundarEgenskapsgrans,vertikalAvgransning
    -> JSONExtractor_b_varde
JSONExtractor_b_varde
    EXTRACT_QUERY_TABLE = bestammelsevarde json["bestammelsevarde"]
    JSON_DOCUMENT = @Value(text_line_data)
    READ_FROM_FILE = NO
    EVALUATED -> FeatureMerger_2 [REQUESTOR]
AttributeKeeper_10
    CREATE_BULK_MODE_FEATURES = NO
    KEEP_ATTRS = beteckning_old,index_old,objektidentitet,galler_all_anvandningsform
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(objektidentitet) @Value(objektidentitet) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> JSONExtractor_kvalitet
    UNMERGED_REQUESTOR -> JSONExtractor_kvalitet
JSONExtractor_kvalitet
    EXTRACT_QUERY_TABLE = kvalitetsbeskrivning json["kvalitetsbeskrivning"]
    JSON_DOCUMENT = @Value(text_line_data)
    READ_FROM_FILE = NO
    EVALUATED -> FeatureJoiner_b_kv [LEFT]
FeatureJoiner_b_kv
    ATTR_CONFLICT_RES_LOOKUP = USE_LEFT
    GEOMETRY_HANDLING_LOOKUP = USE_LEFT
    JOIN_KEYS = kvalitetsbeskrivning text_line_data AUTO
    JOIN_MODE = Inner
    ATTR_CONFLICT_RES = Use Left
    GEOMETRY_HANDLING = Use Left
    JOINED -> DuplicateFilter_3
    JOINED -> FeatureJoiner_3 [LEFT]
    UNJOINED_LEFT -> DuplicateFilter_3
    UNJOINED_LEFT -> FeatureJoiner_3 [LEFT]
DuplicateFilter_3
    INPUT_ORDERED_CHOICE_LOOKUP = NO
    KEYATTR = bestammelsevarde planbestammelsekatalogreferens
    PRESERVE_FEATURE_ORDER_LOOKUP = PER_OUTPUT_PORT
    INPUT_ORDERED_CHOICE = No
    UNIQUE -> UUIDGen_best_uuid
UUIDGen_best_uuid: UUIDGenerator
    UUID_ATTR = best_uuid
    -> FeatureJoiner_bkat [LEFT]
    -> keep_variabel
bkatalog_imp (reader POSTGRES_1)
    attributes: katalogversion text,BTree, bestammelsetyp_name text, anvandningsform_name text, huvudmannaskap_name text, kategorienligtboverketsallmannarad text, underkategorienligtboverketsallmannarad text, anvandningsslag text, bestammelseformulering text, uttrycktvarde text, enligtboverketsallmannarad text, beteckning text, lagstod text, kapitel text, paragraf text, stycke text, punkt text, forklaring text, farg_id int4, farg text, borjargalla date, slutargalla date, bestammelsekod text, redigerad date, publicerad date, id uuid,BTree, symbolbeteckning_type text, symbolbeteckning_updated text, symbolbeteckning_id int8, symbolbeteckning_name text, geometrityp text
    -> AttributeKeeper_12
AttributeKeeper_12
    CREATE_BULK_MODE_FEATURES = NO
    KEEP_ATTRS = beteckning,id,anvandningsform_name,kategorienligtboverketsallmannarad,underkategorienligtboverketsallmannarad,symbolbeteckning_name
    -> AttributeManager_22
AttributeManager_22
    ATTR_TABLE:
      RENAME_SET_VALUE anvandningsform_name > anvandningsform
      RENAME_SET_VALUE kategorienligtboverketsallmannarad > kategori
      RENAME_SET_VALUE underkategorienligtboverketsallmannarad > underkategori
    -> FeatureJoiner_bkat [RIGHT]
FeatureJoiner_bkat
    ATTR_CONFLICT_RES_LOOKUP = USE_LEFT
    GEOMETRY_HANDLING_LOOKUP = USE_LEFT
    JOIN_KEYS = planbestammelsekatalogreferens id AUTO
    JOIN_MODE = Inner
    ATTR_CONFLICT_RES = Use Left
    GEOMETRY_HANDLING = Use Left
    JOINED -> Tester_bet_from_variabel
Tester_bet_from_variabel
    BOOL_OP = OR
    TEST_CLAUSE:
      CASE_INSENSITIVE_TEST @Value(beteckning) BEGINS_WITH [
      CASE_INSENSITIVE_TEST @Value(symbolbeteckning_name) BEGINS_WITH Högsta
      CASE_INSENSITIVE_TEST @Value(symbolbeteckning_name) BEGINS_WITH Takvinkel
    TEST_MODE = CASE_INSENSITIVE_TEST
    PASSED -> join_attrib
    FAILED -> Tester_not_old_bet
join_attrib: AttributeManager
    ATTR_TABLE = SET_TO join_beskrivning (varchar(200)) = FME_CONDITIONAL:DEFAULT_VALUE'_FME_NO_OP_'BOOL_OP;OR;COMPOSITE_TEST;1;CASE_INSENSITIVE_TEST @Value(beteckning) BEGINS_WITH ['@Substring(@Value(beteckning),1,@FindString(@Value(beteckning),:,0,caseSensitive=TRUE)-1)'BOOL_OP;OR;COMPOSITE_TEST;1;CASE_INSENSITIVE_TEST @Value(symbolbeteckning_name) BEGINS_WITH Högsta'hojd'BOOL_OP;OR;COMPOSITE_TEST;1;CASE_INSENSITIVE_TEST @Value(symbolbeteckning_name) BEGINS_WITH Takvinkel'takvinkel'FME_NUM_CONDITIONS4___
    -> FeatureJoiner_6 [LEFT]
FeatureJoiner_6
    ATTR_CONFLICT_RES_LOOKUP = USE_LEFT
    GEOMETRY_HANDLING_LOOKUP = USE_LEFT
    JOIN_KEYS = best_uuid best_uuid AUTO join_beskrivning beskrivning AUTO
    JOIN_MODE = Inner
    ATTR_CONFLICT_RES = Use Left
    GEOMETRY_HANDLING = Use Left
    JOINED -> bet_from_variabel
bet_from_variabel: AttributeManager
    ATTR_TABLE:
      REMOVE join_beskrivning
      SET_TO beteckning = FME_CONDITIONAL:DEFAULT_VALUE'@Value(variabelvarde)#'BOOL_OP;OR;COMPOSITE_TEST;1;TEST symbolbeteckning_name ATTRIBUTE_HAS_A_VALUE _FME_BLANK_STRING_'@Value(variabelvarde)'FME_NUM_CONDITIONS2___
      REMOVE datatyp
      REMOVE variabelvarde
      REMOVE beskrivning
      REMOVE vardetyp
      REMOVE enhet
    -> Tester_not_old_bet
Tester_not_old_bet
    BOOL_OP = AND
    TEST_CLAUSE:
      TEST beteckning_old ATTRIBUTE_IS_MISSING ""
      TEST Label ATTRIBUTE_IS_MISSING ""
    TEST_MODE = TEST
    PASSED -> Tester_index_hash
    FAILED -> get_old_bet_and_index
Tester_index_hash
    BOOL_OP = OR
    TEST_CLAUSE = CASE_INSENSITIVE_TEST @Value(beteckning) ENDS_WITH #
    TEST_MODE = CASE_INSENSITIVE_TEST
    PASSED -> Trim_hash
    FAILED -> Slutfix_best
Trim_hash: AttributeTrimmer
    SRC_ATTRS = beteckning
    TRIM_CHARS = #
    TRIM_TO_NONE = Yes
    TRIM_TYPE_TCL = trimright
    TRIM_TYPE = Right
    -> Counter_index
Counter_index
    CNT_ATTR = index
    DOMAIN = @Value(beteckning)
    SCOPE = Global
    START = 1
    SCOPEVAR = Global
    -> Slutfix_best
get_old_bet_and_index: AttributeManager
    ATTR_TABLE:
      REMOVE beteckning (buffer)
      SET_TO beteckning (buffer) = FME_CONDITIONAL:DEFAULT_VALUE'@Value(beteckning_old)'BOOL_OP;OR;COMPOSITE_TEST;1;TEST Label ATTRIBUTE_HAS_A_VALUE _FME_BLANK_STRING_'@Value(Label)'FME_NUM_CONDITIONS2___
      SET_TO index (varchar(200)) = FME_CONDITIONAL:DEFAULT_VALUE'@Value(index_old)'BOOL_OP;OR;COMPOSITE_TEST;1;TEST Index ATTRIBUTE_HAS_A_VALUE _FME_BLANK_STRING_'@Value(Index)'FME_NUM_CONDITIONS2___
    -> Slutfix_best
Slutfix_best: AttributeManager
    ATTR_TABLE:
      RENAME_SET_VALUE feature:typ > bestammelsetyp = FME_CONDITIONAL:DEFAULT_VALUE'_FME_NO_OP_'BOOL_OP;OR;COMPOSITE_TEST;1;TEST @Value(bestammelsetyp) = användningsbestämmelse'Användning'BOOL_OP;OR;COMPOSITE_TEST;1;TEST @Value(bestammelsetyp) = egenskapsbestämmelse'Egenskap'BOOL_OP;OR;COMPOSITE_TEST;1;TEST @Value(bestammelsetyp) = administrativ bestämmelse'Administrativ'FME_NUM_CONDITIONS4___
      RENAME_SET_VALUE detaljplan > plan_uuid
      RENAME_SET_VALUE planbestammelsekatalogreferens > bk_ref
      RENAME_SET_VALUE ursprungligBestammelseformulering > ursprunglig
      SET_TO anvandningsform = @TitleCase(@Value(anvandningsform))
      SET_TO kategori = @TitleCase(@Value(kategori))
      SET_TO underkategori = FME_CONDITIONAL:DEFAULT_VALUE'_FME_NO_OP_'BOOL_OP;OR;COMPOSITE_TEST;1;TEST underkategori ATTRIBUTE_HAS_A_VALUE _FME_BLANK_STRING_'@TitleCase(@Value(underkategori))'FME_NUM_CONDITIONS2___
      RENAME_SET_VALUE beskrivningAnvandbarhet > anvandbarhet_beskrivning
      REMOVE planbestammelsebeskrivning.motiv
      RENAME_SET_VALUE id > kvalitet
      SET_TO beteckning = FME_CONDITIONAL:DEFAULT_VALUE'@Value(beteckning)'BOOL_OP;OR;COMPOSITE_TEST;1;CASE_INSENSITIVE_TEST @Value(bestammelseformulering) BEGINS_WITH Markens höjd över nollplanet ska vara'@SubstringRegularExpression(@Value(bestammelseformulering),(?<!\d)[0-9]+[.]?[0-9]?)'BOOL_OP;OR;COMPOSITE_TEST;1;TEST vertikalAvgransning ATTRIBUTE_HAS_A_VALUE _FME_BLANK_STRING_'(@Value(beteckning))'FME_NUM_CONDITIONS3___
      SET_TO sekundar = FME_CONDITIONAL:DEFAULT_VALUE'False'BOOL_OP;OR;COMPOSITE_TEST;1;TEST sekundarEgenskapsgrans ATTRIBUTE_HAS_A_VALUE _FME_BLANK_STRING_'@Value(sekundarEgenskapsgrans)'BOOL_OP;OR;COMPOSITE_TEST;1;TEST @Value(bestammelsetyp) = Administrativ'True'FME_NUM_CONDITIONS3___
    -> best (writer POSTGRES_3)
    -> Junction_3
best (writer POSTGRES_3)
    attributes: best_uuid uuid,PrimaryKey, plan_uuid uuid,BTree, bestammelsetyp text, anvandningsform text, kategori text, underkategori text, bk_ref uuid, sekundar bool, galler_all_anvandningsform bool, ursprunglig text, beteckning text, index int2, anvandbarhet text, anvandbarhet_beskrivning text, kval_id uuid
Note: Till bestämmelsegeometrierna
Junction_3
    -> Junction_4

Bookmark: planeringsunderlag
JSONFrag_punderlag: JSONFragmenter
    EXPLODE_FORMAT = JSON
    EXTRACT_ATTR = Yes
    JSON_ATTR = text_line_data
    JSON_QUERY = json["planeringsunderlag"][*]
    NEW_ATTRIBUTES = huvudomrade underlagstyp utredningsunderlag
    READ_FROM_FILE = NO
    RECURSIVE_LOOKUP = YES
    REJECT_EMPTY_LISTS = YES
    RECURSIVE = Yes
    FRAGMENTS -> UUIDGenerator_underlag
UUIDGenerator_underlag
    UUID_ATTR = underlag_id
    -> JSONFrag_underlag
JSONFrag_underlag: JSONFragmenter
    EXPLODE_FORMAT = JSON
    EXTRACT_ATTR = Yes
    JSON_ATTR = text_line_data
    JSON_QUERY = json["underlag"]
    NEW_ATTRIBUTES = namn kortnamn
    READ_FROM_FILE = NO
    RECURSIVE_LOOKUP = YES
    REJECT_EMPTY_LISTS = YES
    RECURSIVE = Yes
    FRAGMENTS -> UUIDGenerator_dokref_3
UUIDGenerator_dokref_3
    UUID_ATTR = dokref_id
    -> AttributeKeeper_4
    -> JSONExtr_datum_hand_3
JSONExtr_datum_hand_3: JSONExtractor
    EXTRACT_QUERY_TABLE = datum json["datum"]["datum"] handelse json["datum"]["handelse"]
    JSON_DOCUMENT = @Value(text_line_data)
    READ_FROM_FILE = NO
    EVALUATED -> AttributeExposer_5
AttributeExposer_5
    ATTR_LIST = specifikReferens{}
    -> ListConcatenator_6
ListConcatenator_6
    DROP_EMPTY_PARTS = No
    LIST_ATTR = specifikReferens{}
    SEP = ,
    VAL_ATTR = specifik_ref
    -> AttributeManager_14
AttributeManager_14
    ATTR_TABLE:
      RENAME_SET_VALUE objektidentitet > plan_uuid
      SET_TO datum = FME_CONDITIONAL:DEFAULT_VALUE'FME_NULL_VALUE'BOOL_OP;OR;COMPOSITE_TEST;1;TEST datum ATTRIBUTE_HAS_A_VALUE _FME_BLANK_STRING_'@Value(datum)'FME_NUM_CONDITIONS2___
      SET_TO handelse = FME_CONDITIONAL:DEFAULT_VALUE'FME_NULL_VALUE'BOOL_OP;OR;COMPOSITE_TEST;1;TEST handelse ATTRIBUTE_HAS_A_VALUE _FME_BLANK_STRING_'@Value(handelse)'FME_NUM_CONDITIONS2___
      RENAME_SET_VALUE utredningsunderlag > underlagstyp
      REMOVE specifikReferens{}
      SET_TO specifik_ref = {@Value(specifik_ref)}
    -> SQL_delete_existing_pu [INITIATOR]
SQL_delete_existing_pu: SQLExecutor
    COMBINE_ATTRS = Result Attributes Only
    COMBINE_GEOM = Initiator Geometry Only
    DATASET = MSF_geodata_fme_user
    FORMAT = POSTGRES
    OUTPUT_FEATURES_DISPLAY = Schema and Data Features
    POSTGRES_CREATE_FEATURE_TABLES_FROM_DATA = Yes
    POSTGRES_NAMED_CONNECTION = geodata_geodata
    POSTGRES_QUERY_FEATURE_TYPES_FOR_MERGE_FILTERS = Yes
    POSTGRES_READ_TIME_WITH_TIMEZONE = Yes
    SQL_STATEMENT = DELETE FROM qdp2.underlag WHERE plan_uuid = '@Value(plan_uuid)';
    INITIATOR -> underlag (writer POSTGRES_3)

Bookmark: planbeskrivning
JSONFrag_planb_2: JSONFragmenter
    EXPLODE_FORMAT = JSON
    EXTRACT_ATTR = Yes
    JSON_ATTR = text_line_data
    JSON_QUERY = json["planbeskrivning"]["planbeskrivning"]
    NEW_ATTRIBUTES = namn kortnamn
    READ_FROM_FILE = NO
    RECURSIVE_LOOKUP = YES
    REJECT_EMPTY_LISTS = YES
    RECURSIVE = Yes
    FRAGMENTS -> UUIDGenerator_planb
UUIDGenerator_planb
    UUID_ATTR = planbeskr_id
    -> UUIDGenerator_dokref_2
UUIDGenerator_dokref_2
    UUID_ATTR = dokref_id
    -> AttributeKeeper_4
    -> JSONExtr_datum_hand_2
JSONExtr_datum_hand_2: JSONExtractor
    EXTRACT_QUERY_TABLE = datum json["datum"]["datum"] handelse json["datum"]["handelse"]
    JSON_DOCUMENT = @Value(text_line_data)
    READ_FROM_FILE = NO
    EVALUATED -> AttributeExposer_6
AttributeExposer_6
    ATTR_LIST = specifikReferens{}
    -> ListConcatenator_7
ListConcatenator_7
    DROP_EMPTY_PARTS = No
    LIST_ATTR = specifikReferens{}
    SEP = ,
    VAL_ATTR = specifik_ref
    -> AttributeManager_13
AttributeManager_13
    ATTR_TABLE:
      RENAME_SET_VALUE objektidentitet > plan_uuid
      SET_TO datum = FME_CONDITIONAL:DEFAULT_VALUE'FME_NULL_VALUE'BOOL_OP;OR;COMPOSITE_TEST;1;TEST datum ATTRIBUTE_HAS_A_VALUE _FME_BLANK_STRING_'@Value(datum)'FME_NUM_CONDITIONS2___
      SET_TO handelse = FME_CONDITIONAL:DEFAULT_VALUE'FME_NULL_VALUE'BOOL_OP;OR;COMPOSITE_TEST;1;TEST handelse ATTRIBUTE_HAS_A_VALUE _FME_BLANK_STRING_'@Value(handelse)'FME_NUM_CONDITIONS2___
      REMOVE specifikReferens{}
      SET_TO specifik_ref = {@Value(specifik_ref)}
    -> SQL_delete_existing_pb [INITIATOR]
SQL_delete_existing_pb: SQLExecutor
    COMBINE_ATTRS = Result Attributes Only
    COMBINE_GEOM = Initiator Geometry Only
    DATASET = MSF_geodata_fme_user
    FORMAT = POSTGRES
    OUTPUT_FEATURES_DISPLAY = Schema and Data Features
    POSTGRES_CREATE_FEATURE_TABLES_FROM_DATA = Yes
    POSTGRES_NAMED_CONNECTION = geodata_geodata
    POSTGRES_QUERY_FEATURE_TYPES_FOR_MERGE_FILTERS = Yes
    POSTGRES_READ_TIME_WITH_TIMEZONE = Yes
    SQL_STATEMENT = DELETE FROM qdp2.planbeskrivning WHERE plan_uuid = '@Value(plan_uuid)';
    INITIATOR -> planbeskrivning (writer POSTGRES_3)

Bookmark: beslutsinformation
JSONFragmenter_beslutsinfo
    EXPLODE_FORMAT = JSON
    EXTRACT_ATTR = Yes
    JSON_ATTR = text_line_data
    JSON_QUERY = json["beslutsinformation"][*]
    NEW_ATTRIBUTES = instansInomKommunen diarienummerKommun diarienummerFullmaktige beslutstyp datumPaborjat datumAntagande genomforandetid genomforandetidStartar arkividentitetKommun
    READ_FROM_FILE = NO
    RECURSIVE_LOOKUP = YES
    REJECT_EMPTY_LISTS = YES
    RECURSIVE = Yes
    FRAGMENTS -> UUIDGenerator_beslut
UUIDGenerator_beslut
    UUID_ATTR = beslut_id
    -> AttributeKeeper_7
    -> AttributeExposer_7
    -> AttributeKeeper_2
AttributeExposer_7
    ATTR_LIST = berordDomsMalnummer{},foregaendePlansBeteckning{},planbestammelse{},datumLagakraft{}
    -> ListConcatenator
ListConcatenator
    DROP_EMPTY_PARTS = No
    LIST_ATTR = datumLagakraft{}
    SEP = ,
    VAL_ATTR = lagakraft
    -> ListConcatenator_2
ListConcatenator_2
    DROP_EMPTY_PARTS = No
    LIST_ATTR = berordDomsMalnummer{}
    SEP = ,
    VAL_ATTR = berord_doms_malnr
    -> ListConcatenator_3
ListConcatenator_3
    DROP_EMPTY_PARTS = No
    LIST_ATTR = foregaendePlansBeteckning{}
    SEP = ,
    VAL_ATTR = foregaende_plans_bet
    -> ListElementCounter_3
ListElementCounter_3
    CNT_ATTR = _best_count
    LIST_NAME = planbestammelse{}
    -> ListConcatenator_4
ListConcatenator_4
    DROP_EMPTY_PARTS = Yes
    LIST_ATTR = planbestammelse{}
    SEP = ,
    VAL_ATTR = planbestammelse
    -> AttributeManager_12
AttributeManager_12
    ATTR_TABLE:
      RENAME_SET_VALUE objektidentitet > plan_uuid
      RENAME_SET_VALUE instansInomKommunen > instans
      RENAME_SET_VALUE diarienummerKommun > diarienummer_kn
      RENAME_SET_VALUE diarienummerFullmaktige > diareinummer_kf
      RENAME_SET_VALUE datumPaborjat > paborjat
      RENAME_SET_VALUE datumAntagande > antagande
      RENAME_SET_VALUE genomforandetidStartar > genomforandetid_startar
      RENAME_SET_VALUE arkividentitetKommun > arkivid_kn
      REMOVE berordDomsMalnummer{}
      REMOVE foregaendePlansBeteckning{}
      REMOVE planbestammelse{}
      REMOVE datumLagakraft{}
      SET_TO lagakraft = {@Value(lagakraft)}
      SET_TO berord_doms_malnr = {@Value(berord_doms_malnr)}
      SET_TO foregaende_plans_bet = {@Value(foregaende_plans_bet)}
      SET_TO planbestammelse = {@Value(planbestammelse)}
      SET_TO _join_dummy_att = 1
    -> FeatureJoiner_8 [LEFT]
FeatureJoiner_8
    ATTR_CONFLICT_RES_LOOKUP = USE_LEFT
    GEOMETRY_HANDLING_LOOKUP = USE_LEFT
    JOIN_KEYS = _join_dummy_att _join_dummy_attribute AUTO
    JOIN_MODE = Inner
    ATTR_CONFLICT_RES = Use Left
    GEOMETRY_HANDLING = Use Left
    JOINED -> SQL_delete_existing_b [INITIATOR]
SQL_delete_existing_b: SQLExecutor
    COMBINE_ATTRS = Result Attributes Only
    COMBINE_GEOM = Initiator Geometry Only
    DATASET = MSF_geodata_fme_user
    FORMAT = POSTGRES
    OUTPUT_FEATURES_DISPLAY = Schema and Data Features
    POSTGRES_CREATE_FEATURE_TABLES_FROM_DATA = Yes
    POSTGRES_NAMED_CONNECTION = geodata_geodata
    POSTGRES_QUERY_FEATURE_TYPES_FOR_MERGE_FILTERS = Yes
    POSTGRES_READ_TIME_WITH_TIMEZONE = Yes
    SQL_STATEMENT = DELETE FROM qdp2.beslut WHERE plan_uuid = '@Value(plan_uuid)';
    INITIATOR -> AttributeManager_21
AttributeManager_21
    ATTR_TABLE = SET_TO planbestammelse = FME_CONDITIONAL:DEFAULT_VALUE'@Value(planbestammelse)'BOOL_OP;OR;COMPOSITE_TEST;1;TEST @Value(_best_count) = @Value(_numfeatures)'FME_NULL_VALUE'FME_NUM_CONDITIONS2___
    -> beslut (writer POSTGRES_3)

Bookmark: grundkarta
AttributeKeeper_2
    CREATE_BULK_MODE_FEATURES = NO
    KEEP_ATTRS = text_line_data,beslut_id
    -> AttributeManager_11
AttributeManager_11
    ATTR_TABLE = RENAME_SET_VALUE beslut_id > dokref_id
    -> JSONFragmenter_grundk
JSONFragmenter_grundk
    EXPLODE_FORMAT = JSON
    EXTRACT_ATTR = Yes
    JSON_ATTR = text_line_data
    JSON_QUERY = json["grundkarta"][*]
    NEW_ATTRIBUTES = identitet lank namnrymd
    READ_FROM_FILE = NO
    RECURSIVE_LOOKUP = YES
    REJECT_EMPTY_LISTS = YES
    RECURSIVE = Yes
    FRAGMENTS -> referens (writer POSTGRES_3)

Bookmark: Beslutshandling
AttributeKeeper_7
    CREATE_BULK_MODE_FEATURES = NO
    KEEP_ATTRS = beslut_id,text_line_data
    -> JSONFragmenter_handl
JSONFragmenter_handl
    EXPLODE_FORMAT = JSON
    EXTRACT_ATTR = Yes
    JSON_ATTR = text_line_data
    JSON_QUERY = json["beslutshandling"][*]
    READ_FROM_FILE = NO
    RECURSIVE_LOOKUP = YES
    REJECT_EMPTY_LISTS = YES
    RECURSIVE = Yes
    FRAGMENTS -> AttributeExposer_8
AttributeExposer_8
    ATTR_LIST = innehall{}
    -> ListConcatenator_8
ListConcatenator_8
    DROP_EMPTY_PARTS = Yes
    LIST_ATTR = innehall{}
    SEP = ,
    VAL_ATTR = innehall
    -> JSONFragmenter_dok
JSONFragmenter_dok
    EXPLODE_FORMAT = JSON
    EXTRACT_ATTR = Yes
    JSON_ATTR = text_line_data
    JSON_QUERY = json["dokument"]
    NEW_ATTRIBUTES = namn kortnamn
    READ_FROM_FILE = NO
    RECURSIVE_LOOKUP = YES
    REJECT_EMPTY_LISTS = YES
    RECURSIVE = Yes
    FRAGMENTS -> UUIDGenerator_dokref
UUIDGenerator_dokref
    UUID_ATTR = dokref_id
    -> JSONExtr_datum_hand
    -> AttributeKeeper_4
JSONExtr_datum_hand: JSONExtractor
    EXTRACT_QUERY_TABLE = datum json["datum"]["datum"] handelse json["datum"]["handelse"]
    JSON_DOCUMENT = @Value(text_line_data)
    READ_FROM_FILE = NO
    EVALUATED -> AttributeExposer_3
AttributeExposer_3
    ATTR_LIST = specifikReferens{}
    -> ListConcatenator_5
ListConcatenator_5
    DROP_EMPTY_PARTS = Yes
    LIST_ATTR = specifikReferens{}
    SEP = ,
    VAL_ATTR = specifik_ref
    -> UUID_besluthandling
UUID_besluthandling: UUIDGenerator
    UUID_ATTR = beslh_id
    -> AttributeManager_17
AttributeManager_17
    ATTR_TABLE:
      SET_TO datum = FME_CONDITIONAL:DEFAULT_VALUE'FME_NULL_VALUE'BOOL_OP;OR;COMPOSITE_TEST;1;TEST datum ATTRIBUTE_HAS_A_VALUE _FME_BLANK_STRING_'@Value(datum)'FME_NUM_CONDITIONS2___
      SET_TO handelse = FME_CONDITIONAL:DEFAULT_VALUE'FME_NULL_VALUE'BOOL_OP;OR;COMPOSITE_TEST;1;TEST handelse ATTRIBUTE_HAS_A_VALUE _FME_BLANK_STRING_'@Value(handelse)'FME_NUM_CONDITIONS2___
      SET_TO specifik_ref = {@Value(specifik_ref)}
      SET_TO innehall = {@Value(innehall)}
      REMOVE specifikReferens{}
      REMOVE innehall{}
    -> beslutshandling (writer POSTGRES_4)

Bookmark: referens
AttributeKeeper_4
    CREATE_BULK_MODE_FEATURES = No
    KEEP_ATTRS = text_line_data,dokref_id
    -> JSONFragmenter_ref
JSONFragmenter_ref
    EXPLODE_FORMAT = JSON
    EXTRACT_ATTR = Yes
    JSON_ATTR = text_line_data
    JSON_QUERY = json["referens"][*]
    NEW_ATTRIBUTES = identitet lank namnrymd
    READ_FROM_FILE = NO
    RECURSIVE_LOOKUP = YES
    REJECT_EMPTY_LISTS = YES
    RECURSIVE = Yes
    FRAGMENTS -> referens (writer POSTGRES_3)

Bookmark: Till beslutsinformtion
AttributeManager_20
    ATTR_TABLE:
      REMOVE text_line_data
      REMOVE json_type
      REMOVE json_index
      REMOVE feature:typ
      REMOVE objektidentitet
      SET_TO _join_dummy_attribute = 1
    -> Sampler
Sampler
    MODE = ORIGINAL
    RATE = 1
    SAMPLE_TYPE_MULTIPLIER = -1
    SAMPLE_MODE = No
    SAMPLE_TYPE_LONG = First N Features
    SAMPLED -> Junction
Note: Beslutsinfo
Junction
    -> Junction_2

Bookmark: Hämta ev befintliga best
SQLExecutor
    COMBINE_ATTRS = Result Attributes Only
    COMBINE_GEOM = Initiator Geometry Only
    DATASET = MSF_geodata_fme_user
    EXPOSED_ATTRIBUTE_LIST = objektidentitet,motiv_id,motiv,huvudsaklig,norr,ost,rotation,beteckning,index,galler_all_anvandningsform
    FORMAT = POSTGRES
    OUTPUT_FEATURES_DISPLAY = Schema and Data Features
    POSTGRES_CREATE_FEATURE_TABLES_FROM_DATA = Yes
    POSTGRES_NAMED_CONNECTION = geodata_geodata
    POSTGRES_QUERY_FEATURE_TYPES_FOR_MERGE_FILTERS = Yes
    POSTGRES_READ_TIME_WITH_TIMEZONE = Yes
    SQL_STATEMENT:
      SELECT a.objektidentitet, COALESCE(m.motiv_id,m2.motiv_id) AS motiv_id, COALESCE(m.motiv,m2.motiv) AS motiv, a.huvudsaklig, a.norr, a.ost, a.rotation
      ,b.beteckning, b.index, b.galler_all_anvandningsform
      FROM
      (SELECT abest_uuid AS objektidentitet, best_uuid, motiv_id, huvudsaklig, norr, ost, rotation FROM qdp2.anv_best
       UNION
       SELECT ebest_uuid AS objektidentitet, best_uuid, motiv_id, NULL AS huvudsaklig, norr, ost, rotation FROM qdp2.egen_best
       UNION
       SELECT l_uuid AS objektidentitet, best_uuid, motiv_id, NULL AS huvudsaklig, NULL AS norr, NULL AS ost, NULL AS rotation FROM qdp2.egenlin
       UNION
       SELECT p_uuid AS objektidentitet, best_uuid, motiv_id, NULL AS huvudsaklig, NULL AS norr, NULL AS ost, NULL AS rotation FROM qdp2.egenpkt
       UNION
       SELECT best_uuid AS objektidentitet, best_uuid, NULL AS motiv_id, NULL AS huvudsaklig, NULL AS norr, NULL AS ost, NULL AS rotation
      			FROM qdp2.best WHERE galler_all_anvandningsform = true
      )a
      JOIN qdp2.best b ON a.best_uuid = b.best_uuid
      LEFT JOIN qdp2.motiv m ON a.motiv_id = m.motiv_id
      LEFT JOIN qdp2.motiv m2 ON b.best_uuid = m2.best_uuid AND (m2.motiv_id != a.motiv_id OR a.motiv_id IS NULL)
      WHERE b.plan_uuid = '@Value(objektidentitet)'
    RESULT -> AttributeManager_10
AttributeManager_10
    ATTR_TABLE:
      RENAME_SET_VALUE motiv > planbestammelsebeskrivning.motiv
      RENAME_SET_VALUE norr > norr_b
      RENAME_SET_VALUE ost > ost_b
      RENAME_SET_VALUE beteckning > beteckning_old
      RENAME_SET_VALUE index > index_old
    USER_EXPOSED_ATTRIBUTES = bk_ref,index,abest_uuid
    -> FeatureMerger [SUPPLIER]
    -> AttributeKeeper_10

Bookmark: Variabler
keep_variabel: AttributeKeeper
    CREATE_BULK_MODE_FEATURES = No
    KEEP_ATTRS = best_uuid,bestammelsevarde
    -> Tester_finns
Tester_finns
    BOOL_OP = AND
    TEST_CLAUSE:
      TEST bestammelsevarde ATTRIBUTE_HAS_A_VALUE ""
      TEST @Value(bestammelsevarde) NOT_= []
    TEST_MODE = TEST
    PASSED -> JSONFragmenter
JSONFragmenter
    EXPLODE_FORMAT = JSON
    EXTRACT_ATTR = Yes
    JSON_ATTR = bestammelsevarde
    JSON_QUERY = json[*]
    NEW_ATTRIBUTES = datatyp variabelvarde beskrivning vardetyp enhet
    READ_FROM_FILE = NO
    RECURSIVE_LOOKUP = YES
    REJECT_EMPTY_LISTS = YES
    RECURSIVE = Yes
    FRAGMENTS -> variabel (writer POSTGRES_5)
    FRAGMENTS -> FeatureJoiner_6 [RIGHT]

Bookmark: Motiv
DuplicateFilter_6
    INPUT_ORDERED_CHOICE_LOOKUP = NO
    KEYATTR = best_uuid planbestammelsebeskrivning.motiv
    PRESERVE_FEATURE_ORDER_LOOKUP = PER_OUTPUT_PORT
    INPUT_ORDERED_CHOICE = No
    UNIQUE -> Tester_2
Tester_2
    BOOL_OP = OR
    TEST_CLAUSE = TEST motiv_id ATTRIBUTE_IS_MISSING ""
    TEST_MODE = TEST
    PASSED -> UUID_motiv
    FAILED -> AttributeManager_16
UUID_motiv: UUIDGenerator
    UUID_ATTR = motiv_id
    -> AttributeManager_16
AttributeManager_16
    ATTR_TABLE:
      REMOVE text_line_data
      REMOVE json_type
      REMOVE json_index
      REMOVE feature:typ
      REMOVE objektidentitet
      REMOVE _count
      REMOVE detaljplan
      REMOVE planbestammelsekatalogreferens
      REMOVE bestammelseformulering
      REMOVE ursprungligBestammelseformulering
      REMOVE anvandningsform
      REMOVE kategori
      REMOVE underkategori
      REMOVE anvandbarhet
      REMOVE beskrivningAnvandbarhet
      RENAME_SET_VALUE planbestammelsebeskrivning.motiv > motiv
      REMOVE reglerarAnvandningsbestammelse{}
      REMOVE bestammelsevarde
      REMOVE kvalitetsbeskrivning
      REMOVE kval_id
    -> FeatureJoiner_7 [RIGHT]
    -> motiv (writer POSTGRES_4)

Bookmark: Bestämmelserelationer med geom
AttributeKeeper_5
    CREATE_BULK_MODE_FEATURES = NO
    KEEP_ATTRS = detaljplan,feature:typ,text_line_data,best_uuid,objektidentitet,motiv_id,anvandningsform,beteckning,index,huvudsaklig,rotation,norr_b,ost_b,vertikalAvgransning,norr_set,ost_set,FontSize,MainRegulation,Rotation
    KEEP_LIST = reglerarAnvandningsbestammelse{}
    -> JSONFragmenter_b_geom
JSONFragmenter_b_geom
    EXPLODE_FORMAT = JSON
    EXTRACT_ATTR = Yes
    JSON_ATTR = text_line_data
    JSON_QUERY = json["bestammelsegeometri"][*]
    READ_FROM_FILE = NO
    RECURSIVE_LOOKUP = YES
    REJECT_EMPTY_LISTS = YES
    RECURSIVE = Yes
    FRAGMENTS -> JSONExtractor_2
JSONExtractor_2
    EXTRACT_QUERY_TABLE = json_geom json["geometri"]
    JSON_DOCUMENT = @Value(text_line_data)
    READ_FROM_FILE = NO
    EVALUATED -> AttributeManager_4
AttributeManager_4
    ATTR_TABLE:
      RENAME_SET_VALUE objektidentitet > xbest_uuid
      RENAME_SET_VALUE vertikalAvgransning > avgransning
    -> DuplicateFilter_4
    -> FeatureJoiner_geom [LEFT]
AttributeKeeper_8
    CREATE_BULK_MODE_FEATURES = NO
    KEEP_ATTRS = g_uuid,typ,b_geom,json_geom
    -> FeatureJoiner_geom [RIGHT]
FeatureJoiner_geom
    ATTR_CONFLICT_RES_LOOKUP = USE_LEFT
    GEOMETRY_HANDLING_LOOKUP = USE_RIGHT
    JOIN_KEYS = json_geom json_geom AUTO
    JOIN_MODE = Inner
    ATTR_CONFLICT_RES = Use Left
    GEOMETRY_HANDLING = Use Right
    JOINED -> CenterPointExtractor
CenterPointExtractor
    CENTX = _inside_x
    CENTY = _inside_y
    CENTZ = _inside_z
    EXTRACTIONMODE = INSIDE
    -> FeatureCounter_guuid
    <REJECTED> -> AttributeFilter_b_typ
FeatureCounter_guuid
    FeatureCounterNewAttrParameter = _num_guuid
    -> FeatureCounter_typ
FeatureCounter_typ
    FeatureCounterNewAttrParameter = _num_ftyp
    -> Sorter_2
Sorter_2
    SORT_PARM = beteckning ALPHA ASCENDING index NUMERIC ASCENDING
    SORTED -> Counter_2
Counter_2
    CNT_ATTR = _count
    GROUP_BY = g_uuid feature:typ
    SCOPE = Local
    START = 0
    -> AttributeManager_norr_ost
AttributeManager_norr_ost
    ATTR_TABLE:
      RENAME_SET_VALUE _inside_x > ost = FME_CONDITIONAL:DEFAULT_VALUE'@Evaluate(@Value(ost) + (@Value(_count)-(@Value(_num_ftyp)-1)/2)*7)'BOOL_OP;OR;COMPOSITE_TEST;1;TEST ost_set ATTRIBUTE_HAS_A_VALUE _FME_BLANK_STRING_'@Value(ost_set)'BOOL_OP;OR;COMPOSITE_TEST;1;TEST ost_b ATTRIBUTE_HAS_A_VALUE _FME_BLANK_STRING_'@Value(ost_b)'FME_NUM_CONDITIONS3___
      RENAME_SET_VALUE _inside_y > norr = FME_CONDITIONAL:DEFAULT_VALUE'_FME_NO_OP_'BOOL_OP;OR;COMPOSITE_TEST;1;TEST norr_set ATTRIBUTE_HAS_A_VALUE _FME_BLANK_STRING_'@Value(norr_set)'BOOL_OP;OR;COMPOSITE_TEST;1;TEST norr_b ATTRIBUTE_HAS_A_VALUE _FME_BLANK_STRING_'@Value(norr_b)'BOOL_OP;AND;COMPOSITE_TEST;1 AND 2;TEST @Value(feature:typ) = användningsbestämmelse;TEST @Value(_num_ftyp) < @Value(_num_guuid)'@Evaluate(@Value(norr)+5)'BOOL_OP;AND;COMPOSITE_TEST;1 AND 2;TEST @Value(feature:typ) = egenskapsbestämmelse;TEST @Value(_num_ftyp) < @Value(_num_guuid)'@Evaluate(@Value(norr)-5)'FME_NUM_CONDITIONS5___
      REMOVE _inside_z
      SET_TO huvudsaklig = FME_CONDITIONAL:DEFAULT_VALUE'False'BOOL_OP;OR;COMPOSITE_TEST;1;TEST MainRegulation ATTRIBUTE_HAS_A_VALUE _FME_BLANK_STRING_'@Value(MainRegulation)'BOOL_OP;OR;COMPOSITE_TEST;1;TEST huvudsaklig ATTRIBUTE_HAS_A_VALUE _FME_BLANK_STRING_'@Value(huvudsaklig)'FME_NUM_CONDITIONS3___
      SET_TO rotation = FME_CONDITIONAL:DEFAULT_VALUE'@Value(rotation)'BOOL_OP;OR;COMPOSITE_TEST;1;TEST Rotation ATTRIBUTE_HAS_A_VALUE _FME_BLANK_STRING_'@Evaluate(360-@Value(Rotation))'FME_NUM_CONDITIONS2___
    USER_EXPOSED_ATTRIBUTES = norr,ost
    -> AttributeFilter_b_typ
AttributeFilter_b_typ
    ATTR_NAME = feature:typ
    ATTR_VALUES = användningsbestämmelse,egenskapsbestämmelse,administrativ bestämmelse,<Empty>,<Missing>,<Null>,<Unfiltered>
    PRESERVE_FEATURE_ORDER_LOOKUP = PER_OUTPUT_PORT
    användningsbestämmelse -> AttributeKeeper_9
    användningsbestämmelse -> AttributeManager_7
    egenskapsbestämmelse -> GeometryFilter
    egenskapsbestämmelse -> AttributeKeeper_11
    administrativ bestämmelse -> AttributeKeeper_11
    administrativ bestämmelse -> GeometryFilter

Bookmark: Användningsbestämmelser, kopplade
AttributeManager_7
    ATTR_TABLE:
      RENAME_SET_VALUE xbest_uuid > abest_uuid
      REMOVE reglerarAnvandningsbestammelse{}
      REMOVE json_type
      REMOVE json_index
      REMOVE b_geom
      RENAME_SET_VALUE g_uuid > o_uuid
      REMOVE typ
      REMOVE _count
      REMOVE fme_rejection_code
    -> anv_best (writer POSTGRES_5)
anv_best (writer POSTGRES_5)
    attributes: abest_uuid uuid,PrimaryKey, best_uuid uuid,BTree, o_uuid uuid,BTree, huvudsaklig bool, norr numeric(10,3), ost numeric(10,3), rotation numeric(10,3), motiv_id uuid, avgransning text, giltighetstid int4, borjar_galla_efter int4

Bookmark: Gäller all
AttributeKeeper_11
    CREATE_BULK_MODE_FEATURES = NO
    KEEP_ATTRS = anvandningsform,best_uuid,typ,g_uuid,xbest_uuid,motiv_id,norr,ost,rotation,avgransning
    -> GeometryFilter_2
GeometryFilter_2
    BREAK_AGG_BOOL = 0
    GEOM_PORTS = AREA LINE POINT
    BREAK_AGG = No
    GEOM_PORT_NAMES = Area Line Point
    AREA -> AttributeManager_9
    AREA -> DuplicateFilter_7
DuplicateFilter_7
    INPUT_ORDERED_CHOICE_LOOKUP = NO
    KEYATTR = xbest_uuid
    PRESERVE_FEATURE_ORDER_LOOKUP = PER_OUTPUT_PORT
    INPUT_ORDERED_CHOICE = No
    DUPLICATE -> Aggregator_4
Aggregator_4
    ACCUM_ATTRS = One
    GROUP_BY = best_uuid xbest_uuid
    MODE = Attributes Only
    SEP = ,
    ACCUM_ATTRS_NAME = Use Attributes From One Feature
    AGGREGATE -> AttributeManager_8
AttributeManager_8
    ATTR_TABLE:
      REMOVE anvandningsform
      REMOVE typ
      SET_TO galler_all_anvandningsform = True
    -> FeatureJoiner_ej_all [RIGHT]
    -> AttributeManager_19
AttributeManager_19
    ATTR_TABLE:
      RENAME_SET_VALUE best_uuid > best_uuid_old
      RENAME_SET_VALUE xbest_uuid > best_uuid
    -> best (writer POSTGRES_6)
AttributeManager_9
    ATTR_TABLE:
      REMOVE anvandningsform
      RENAME_SET_VALUE xbest_uuid > ebest_uuid
      RENAME_SET_VALUE g_uuid > o_uuid
      REMOVE typ
    -> FeatureJoiner_ej_all [LEFT]
FeatureJoiner_ej_all
    ATTR_CONFLICT_RES_LOOKUP = USE_LEFT
    GEOMETRY_HANDLING_LOOKUP = USE_LEFT
    JOIN_KEYS = best_uuid best_uuid AUTO
    JOIN_MODE = Inner
    ATTR_CONFLICT_RES = Use Left
    GEOMETRY_HANDLING = Use Left
    UNJOINED_LEFT -> FeatureJoiner_endast_y [LEFT]
FeatureJoiner_endast_y
    ATTR_CONFLICT_RES_LOOKUP = USE_LEFT
    GEOMETRY_HANDLING_LOOKUP = USE_LEFT
    JOIN_KEYS = ebest_uuid xbest_uuid AUTO
    JOIN_MODE = Inner
    ATTR_CONFLICT_RES = Use Left
    GEOMETRY_HANDLING = Use Left
    JOINED -> egen_best (writer POSTGRES_5)

Bookmark: Egenskapsbestämmelse Gäller endast användning?
GeometryFilter
    BREAK_AGG_BOOL = 0
    GEOM_PORTS = AREA POINT LINE
    BREAK_AGG = No
    GEOM_PORT_NAMES = Area Point Line
    AREA -> Clipper [CLIPPEE]
    POINT -> PointOnAreaOverlayer [POINT]
    LINE -> LineOnAreaOverlayer [LINE]
AttributeKeeper_9
    CREATE_BULK_MODE_FEATURES = No
    KEEP_ATTRS = anvandningsform,best_uuid,xbest_uuid
    -> PointOnAreaOverlayer [AREA]
    -> LineOnAreaOverlayer [AREA]
    -> Clipper [CLIPPER]
Clipper
    BOUNDARY = INSIDE
    CLEANING_TOLERANCE_LOOKUP = AUTO
    CLIPPED_ATTR = _clipped
    LINES_AS_SEGMENTS_LOOKUP = NO
    MEASURE_TYPE_LOOKUP = CONTINUOUS
    MISSING_VAL_MODE_LOOKUP = COMPUTE_NANS
    MULTI_CLIP = YES
    PRESERVE_CLIPPEE_EXTENTS_LOOKUP = NO
    VAL_SOURCE_LOOKUP = CLIPPEE
    BOUNDARY_CASES = Treat as Inside
    CLEANING_TOLERANCE = Automatic
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> CenterPointReplacer
CenterPointReplacer
    POINTTYPE = INSIDE
    POINT -> PointOnAreaOverlayer [POINT]
PointOnAreaOverlayer
    DEAGGREGATE_INPUT = Yes
    GROUP_BY = anvandningsform
    LIST_ATTRS_TO_INCLUDE = anvandningsform xbest_uuid best_uuid
    LIST_NAME = hit_anv_best
    OV_ATTR = _overlaps
    POLYS_FIRST = NO
    POINT -> ListExploder
LineOnAreaOverlayer
    CLEANING_TOLERANCE_LOOKUP = 0.01
    DEAGGREGATE_INPUT = Yes
    GROUP_BY = anvandningsform
    LIST_ATTRS_TO_INCLUDE = anvandningsform xbest_uuid best_uuid
    LIST_NAME = hit_anv_best
    OVERLAY_TYPE = LINE_ON_AREA
    OV_ATTR = _overlaps
    CLEANING_TOLERANCE = 0.01
    LINE -> ListExploder
ListExploder
    INCOMING_PREFIX = anv_
    INDEX_ATTR = _ele_index
    LIST_ATTR = hit_anv_best{}
    ATTR_ACCUM_MODE = Prefix List Attributes
    ELEMENTS -> Aggregator
Aggregator
    ACCUM_ATTRS = One
    AGGREGATE_TYPE = Homogeneous Collection (If Possible)
    COUNT_ATTR = num_geom
    GROUP_BY = xbest_uuid
    LIST_ATTRS_TO_INCLUDE = anv_xbest_uuid anv_best_uuid
    LIST_NAME = hit_anv_best_uuid
    MODE = Geometry - Assemble One Level
    SEP = ,
    ACCUM_ATTRS_NAME = Use Attributes From One Feature
    AGGREGATE -> ListDuplicateRemover
ListDuplicateRemover
    SRC_LIST = hit_anv_best_uuid{}.anv_xbest_uuid
    -> ListElementCounter
AttributeManager_3
    ATTR_TABLE = SET_TO galler_endast = FME_CONDITIONAL:DEFAULT_VALUE'FME_NULL_VALUE'BOOL_OP;OR;COMPOSITE_TEST;1;TEST @Value(_element_count_hit) > @Value(_element_count_reg)'{@Value(_concatenated_reg)}'FME_NUM_CONDITIONS2___
    -> AttributeKeeper_13
AttributeKeeper_13
    CREATE_BULK_MODE_FEATURES = NO
    KEEP_ATTRS = best_uuid,galler_endast,xbest_uuid
    -> DuplicateFilter_5

Bookmark: jämför listorna
ListElementCounter
    CNT_ATTR = _element_count_reg
    LIST_NAME = reglerarAnvandningsbestammelse{}
    -> ListElementCounter_2
ListElementCounter_2
    CNT_ATTR = _element_count_hit
    LIST_NAME = hit_anv_best_uuid{}
    -> ListConcatenator_reg
ListConcatenator_reg
    DROP_EMPTY_PARTS = No
    LIST_ATTR = reglerarAnvandningsbestammelse{}
    SEP = ,
    VAL_ATTR = _concatenated_reg
    -> AttributeManager_3

FME custom transformer FeatureCounter
This transformer counts the number of features passing through, and applies that number as an attribute onto each feature.
It differs from the Counter in that it gives the total count to each feature. It doesn't give each feature a unique, incremented number.
It differs from the StatisticsCalculator in that it does not need an attribute to be selected for analysis.
An optional group-by parameter allows features to be counted in groups.
Transformer Category: Calculated Values
Blocker Transformer: Yes

Parameters:
- GroupBox =   # Group Processing
- GROUP_BY =   # "" Group By
- GROUP_BY_MODE = No   # When All Features Received,No%When Group Changes (Advanced),Yes Complete Groups
- GeneralBox =   # FeatureCounterNewAttrParameter General
- FeatureCounterNewAttrParameter = _numfeatures   # New Attribute Name

Input (input)
    -> AttributeCreator_2
Note: Create temporary attribute for StatisticsCalculator
AttributeCreator_2
    ATTR_TABLE = SET_TO FeatureCounter_tempattr (int8) = 1
    -> StatisticsCalculator
Note: Calculate number of features
StatisticsCalculator
    ATTR_ACCUM_MODE = None
    CALCULATION_MODE = NUMERIC
    FEAT_STATS = FeatureCounter_tempattr,NUMERIC_MODE,,,COUNT,,,,,,,,,,
    GROUP_BY = $(GROUP_BY)
    PREPEND_ATTR_NAME_OBS = No
    STATISTIC_SUFFIX_RENAME_MAP = COUNT,FeatureCounter_tempattr_count
    COMPLETE -> AttributeCreator
Note: Create new attribute
AttributeCreator
    ATTR_TABLE = SET_TO $(FeatureCounterNewAttrParameter) (uint64) = @Value(FeatureCounter_tempattr_count)
    -> AttributeExposer
Note: Expose new attribute
AttributeExposer
    ATTR_LIST = $(FeatureCounterNewAttrParameter)
    -> Output (output)
Note: Output features keeping only new attribute
Output (output)
